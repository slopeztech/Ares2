[DOCUMENT]
TITLE: 3. AMS — Mission Script Engine

[GRAMMAR]
ELEMENTS:
- TAG: REQUIREMENT
  FIELDS:
  - TITLE: UID
    TYPE: String
    REQUIRED: True
  - TITLE: STATUS
    TYPE: SingleChoice(Draft, Active, Deprecated)
    REQUIRED: True
  - TITLE: TAGS
    TYPE: Tag
    REQUIRED: False
  - TITLE: STATEMENT
    TYPE: String
    REQUIRED: True
  - TITLE: VERIFICATION
    TYPE: SingleChoice(Test, Inspection, Analysis, Review)
    REQUIRED: False
  - TITLE: RATIONALE
    TYPE: String
    REQUIRED: False
  - TITLE: REFS
    TYPE: String
    REQUIRED: False

[[SECTION]]
TITLE: 3.1 Script Lifecycle

[REQUIREMENT]
UID: SRS-2000
STATUS: Active
TAGS: AMS, Lifecycle
STATEMENT: The engine shall hold at most one active AMS script at a time. Activating a new script while one is already active shall deactivate the current script first, discarding its runtime state.
VERIFICATION: Inspection
RATIONALE: AMS-1. Single-script constraint eliminates ambiguous state ownership and ensures deterministic resource use.
REFS: docs/standards/ams_standard.md AMS-1

[REQUIREMENT]
UID: SRS-2001
STATUS: Active
TAGS: AMS, Lifecycle, Storage
STATEMENT: AMS scripts shall be stored as UTF-8 plain-text files with extension .ams in the LittleFS directory /missions. The engine shall reject any script larger than AMS_MAX_SCRIPT_BYTES (4096 bytes) with a parse error. No partial loading is permitted.
VERIFICATION: Test
RATIONALE: AMS-2 / config.h AMS_MAX_SCRIPT_BYTES. Bounding script size ensures worst-case flash read time and line-buffer usage remain predictable.
REFS: docs/standards/ams_standard.md AMS-2, src/config.h AMS_MAX_SCRIPT_BYTES

[REQUIREMENT]
UID: SRS-2002
STATUS: Active
TAGS: AMS, Lifecycle, Security
STATEMENT: AMS script filenames accepted by POST /api/mission/activate shall contain only characters from ``[a-zA-Z0-9_\-.]``, shall not contain the sequence "..", and shall not exceed MISSION_FILENAME_MAX (32) characters including the .ams extension. Filenames violating these constraints shall be rejected with HTTP 400.
VERIFICATION: Test
RATIONALE: AMS-2 / CERT-11. Prevents path traversal attacks on the LittleFS volume and ensures cross-platform filename compatibility.
REFS: docs/standards/ams_standard.md AMS-2, docs/standards/cert_standard.md CERT-11, src/config.h MISSION_FILENAME_MAX

[REQUIREMENT]
UID: SRS-2003
STATUS: Active
TAGS: AMS, Lifecycle
STATEMENT: The engine lifecycle shall progress through the states IDLE → LOADED (after activate) → RUNNING (after arm) → IDLE or ERROR. Transitions between lifecycle states shall only occur via the defined API methods: activate(), arm(), deactivate(), and tick(). External code shall not modify lifecycle state directly.
VERIFICATION: Inspection
RATIONALE: AMS-1. Enforces a deterministic FSM for engine lifecycle management and prevents race conditions from concurrent API calls.
REFS: docs/standards/ams_standard.md AMS-1

[REQUIREMENT]
UID: SRS-2004
STATUS: Active
TAGS: AMS, Lifecycle, Storage, Security
STATEMENT: The path used to open an AMS script file shall be constructed by concatenating MISSION_DIR ("/missions/") with the validated script name. The engine shall never call LittleFS open() with a path derived directly from an unvalidated user-supplied string.
VERIFICATION: Inspection
RATIONALE: CERT-11. Defence-in-depth measure: even if SRS-2002 validation is bypassed, path construction from a known prefix prevents directory traversal outside /missions.
REFS: docs/standards/cert_standard.md CERT-11, src/config.h MISSION_DIR

[[/SECTION]]

[[SECTION]]
TITLE: 3.2 State Machine

[REQUIREMENT]
UID: SRS-2100
STATUS: Active
TAGS: AMS, StateMachine
STATEMENT: A single AMS script shall define at most AMS_MAX_STATES (16) states. Each state name shall be at most AMS_MAX_STATE_NAME-1 (15) characters (excluding the NUL terminator). A script that violates either bound shall be rejected at parse time.
VERIFICATION: Test
RATIONALE: config.h constants. Bounds StateDef array size; ensures state names fit in checkpoint records and telemetry EVENT text without truncation.
REFS: src/config.h AMS_MAX_STATES, AMS_MAX_STATE_NAME

[REQUIREMENT]
UID: SRS-2101
STATUS: Active
TAGS: AMS, StateMachine, Transitions
STATEMENT: Each state shall declare at most AMS_MAX_TRANSITIONS (4) transitions. Each transition shall evaluate at most AMS_MAX_TRANSITION_CONDS (4) sub-conditions joined by AND semantics. Transitions shall be evaluated every tick in declaration order; the first matching transition fires and the tick evaluation for that state ends immediately.
VERIFICATION: Test
RATIONALE: AMS-4.6. Declaration-order priority is deterministic and verifiable at review time. Bounded transition count ensures O(1) evaluation per tick.
REFS: docs/standards/ams_standard.md AMS-4.6, src/config.h AMS_MAX_TRANSITIONS, AMS_MAX_TRANSITION_CONDS

[REQUIREMENT]
UID: SRS-2102
STATUS: Active
TAGS: AMS, StateMachine, Transitions
STATEMENT: When a transition fires (normal, fallback, or error-recovery), the engine shall execute exitStateLocked() for the departing state — which runs on_exit: set actions synchronously then dispatches the on_exit: EVENT immediately — before calling enterStateLocked() for the new state.
VERIFICATION: Inspection
RATIONALE: AMS-4.16 / AMS-5.8. Guarantees the farewell telemetry event arrives on the radio bus before the on_enter: event of the new state, preserving chronological event ordering for ground operators.
REFS: docs/standards/ams_standard.md AMS-4.16, AMS-5.8

[REQUIREMENT]
UID: SRS-2103
STATUS: Active
TAGS: AMS, StateMachine, Transitions
STATEMENT: A transition condition qualified with "for Nms" shall not fire until the compound condition has been continuously true for at least N milliseconds, measured from the last state entry or last time the condition became false. The hold timer shall reset to zero whenever any sub-condition in the compound becomes false.
VERIFICATION: Test
RATIONALE: AMS-4.6.1. Prevents spurious transitions triggered by transient sensor noise spikes shorter than N ms.
REFS: docs/standards/ams_standard.md AMS-4.6.1

[REQUIREMENT]
UID: SRS-2104
STATUS: Active
TAGS: AMS, StateMachine, TC
STATEMENT: A TC.command transition condition shall consume the pending TC token atomically at the moment the transition fires. A consumed token shall not satisfy any subsequent TC.command condition within the same tick or any later tick until a new TC command is injected.
VERIFICATION: Test
RATIONALE: AMS-5.3. Prevents double-execution of one-shot commands such as LAUNCH or ABORT, which could cause unintended pyro firing.
REFS: docs/standards/ams_standard.md AMS-5.3

[REQUIREMENT]
UID: SRS-2105
STATUS: Active
TAGS: AMS, StateMachine, Fallback
STATEMENT: If a state declares "fallback transition to STATE after Nms" and no regular transition has fired within N milliseconds of state entry, the fallback transition shall fire unconditionally, bypassing all guard conditions and TC checks. This is the mechanism of last resort for stuck states.
VERIFICATION: Test
RATIONALE: AMS-4.9.2. Prevents permanent state traps when sensors are unavailable or TC commands are lost in the RF link.
REFS: docs/standards/ams_standard.md AMS-4.9.2

[REQUIREMENT]
UID: SRS-2106
STATUS: Active
TAGS: AMS, StateMachine, RTOS
STATEMENT: The engine tick() method shall be non-reentrant. It shall be called exclusively from the main loop() task. No other RTOS task shall call tick() directly or indirectly. API handlers that need engine state shall use the mutex-protected snapshot methods.
VERIFICATION: Inspection
RATIONALE: RTOS-4 / AMS-5.1. The tick FSM is not designed for concurrent invocation; re-entrant calls would corrupt transition history, hold-timers, and HK slot counters.
REFS: docs/standards/rtos_standard.md RTOS-4, docs/standards/ams_standard.md AMS-5.1

[[/SECTION]]

[[SECTION]]
TITLE: 3.3 Guard Conditions and Error Handling

[REQUIREMENT]
UID: SRS-2200
STATUS: Active
TAGS: AMS, Guards
STATEMENT: Each state shall declare at most AMS_MAX_CONDITIONS (4) guard conditions. All declared guard conditions shall be evaluated on every tick, after transition evaluation. If one or more conditions are violated in the same tick, all violations shall be logged before the on_error: handler fires.
VERIFICATION: Test
RATIONALE: AMS-4.7 / AMS-5.2. Reporting all violations per tick rather than only the first enables the operator to diagnose the complete failure envelope from a single EVENT frame.
REFS: docs/standards/ams_standard.md AMS-4.7, AMS-5.2, src/config.h AMS_MAX_CONDITIONS

[REQUIREMENT]
UID: SRS-2201
STATUS: Active
TAGS: AMS, Guards, SensorFault
STATEMENT: If a sensor referenced in a guard or transition condition cannot be read due to a driver failure, I2C timeout, or GPS loss-of-fix, the condition shall evaluate as "holds" (no violation raised). The engine shall NOT enter ERROR state due to a transient sensor read failure.
VERIFICATION: Test
RATIONALE: AMS-4.9 / AMS-5.6. Fail-safe default: sensor absence is not itself a mission fault. False alarms from sensor glitches would trigger unintended recovery sequences.
REFS: docs/standards/ams_standard.md AMS-4.9, AMS-5.6

[REQUIREMENT]
UID: SRS-2202
STATUS: Active
TAGS: AMS, Guards, ErrorRecovery
STATEMENT: If an on_error: block declares "transition to STATE", the engine shall execute that transition (including the departing state's on_exit: handler) instead of halting when a guard condition is violated. The engine shall only enter ERROR status if on_error: provides no recovery transition.
VERIFICATION: Test
RATIONALE: AMS-4.10.2. Explicit recovery paths from guard failures allow scripted safe-mode transitions without requiring operator TC input.
REFS: docs/standards/ams_standard.md AMS-4.10.2

[REQUIREMENT]
UID: SRS-2203
STATUS: Active
TAGS: AMS, Guards, Assertions
STATEMENT: A script may declare at most one assert: block containing at most AMS_MAX_ASSERTS (8) directives. Supported directives are: "reachable STATE" (BFS reachability from state[0]), "no_dead_states" (BFS coverage of all declared states), and "max_transition_depth < N" (acyclic DFS longest-path check). All assert directives are evaluated at parse time during activate(). If any directive fails, the script shall be rejected immediately and the engine shall remain in IDLE status with a descriptive error message. No assert directive shall produce runtime traffic or influence in-flight execution.
VERIFICATION: Test
RATIONALE: AMS-4.14. Parse-time structural verification catches unreachable states and unbounded transition chains before flight. Static checking eliminates runtime overhead and avoids the possibility of the assertion mechanism itself contributing to in-flight failure.
REFS: docs/standards/ams_standard.md AMS-4.14, src/config.h AMS_MAX_ASSERTS

[[/SECTION]]

[[SECTION]]
TITLE: 3.4 On-Enter and On-Exit Handlers

[REQUIREMENT]
UID: SRS-2300
STATUS: Active
TAGS: AMS, OnEnter
STATEMENT: On state entry, the engine shall execute on_enter: set actions synchronously (before the next tick evaluates transitions), then queue the on_enter: EVENT for dispatch on the first available arbitration slot. Set actions shall complete before any HK telemetry for the new state is generated.
VERIFICATION: Test
RATIONALE: AMS-4.8 / AMS-5.2. Synchronous set-action execution ensures global variables are populated before telemetry reads them. Queued EVENT dispatch prevents the on_enter: event from blocking the transition that caused the entry.
REFS: docs/standards/ams_standard.md AMS-4.8, AMS-5.2

[REQUIREMENT]
UID: SRS-2301
STATUS: Active
TAGS: AMS, OnExit
STATEMENT: On state departure (normal transition, fallback, or error-recovery), the engine shall execute on_exit: set actions synchronously, then dispatch the on_exit: EVENT immediately (not queued), before calling enterStateLocked() for the new state. The on_exit: EVENT shall be the last action of the departing state.
VERIFICATION: Test
RATIONALE: AMS-4.16 / AMS-5.8. Deterministic ordering: exit-event byte stream is committed to the radio FIFO before the enter-event, preserving chronological event sequence on the ground station.
REFS: docs/standards/ams_standard.md AMS-4.16, AMS-5.8

[REQUIREMENT]
UID: SRS-2302
STATUS: Active
TAGS: AMS, OnExit, Limits
STATEMENT: An on_exit: block shall accept at most AMS_MAX_SET_ACTIONS (4) set actions and at most one EVENT directive. A "transition to" directive inside on_exit: shall be a parse error, reported immediately and the script shall not be activated.
VERIFICATION: Test
RATIONALE: AMS-4.16.2 / AMS-4.16.4 / PO10-3. Bounded resources prevent on_exit from becoming unbounded work. Transitions from on_exit would create ambiguous state-machine semantics: which state "owns" the transition?
REFS: docs/standards/ams_standard.md AMS-4.16.2, AMS-4.16.4

[REQUIREMENT]
UID: SRS-2303
STATUS: Active
TAGS: AMS, OnExit
STATEMENT: The on_exit: handler shall NOT fire in the following situations: (a) deactivate() is called on a running engine, (b) the engine transitions to ERROR status without a recovery transition, (c) checkpoint restore overwrites the current state index without a runtime transition.
VERIFICATION: Inspection
RATIONALE: AMS-4.16.2. These paths do not represent a normal state departure where an exit audit event is meaningful. Firing on_exit in these cases would produce spurious telemetry events that confuse the ground operator.
REFS: docs/standards/ams_standard.md AMS-4.16.2

[[/SECTION]]

[[SECTION]]
TITLE: 3.5 Global Variables and Set Actions

[REQUIREMENT]
UID: SRS-2400
STATUS: Active
TAGS: AMS, Variables
STATEMENT: A script shall declare at most AMS_MAX_VARS (8) global variables using the "var NAME" directive and at most AMS_MAX_CONSTS (8) named constants using "const NAME = VALUE". Variable names shall be at most AMS_VAR_NAME_LEN-1 (15) characters. Both var and const declarations are global to the script, not scoped to a state.
VERIFICATION: Test
RATIONALE: AMS-4.8.1 / config.h. Bounded counts ensure the VarEntry[] and ConstEntry[] arrays fit in static SRAM. Global scope allows set actions in one state to produce values consumed by guard conditions in another.
REFS: docs/standards/ams_standard.md AMS-4.8.1, src/config.h AMS_MAX_VARS, AMS_MAX_CONSTS, AMS_VAR_NAME_LEN

[REQUIREMENT]
UID: SRS-2401
STATUS: Active
TAGS: AMS, Variables, SetActions
STATEMENT: A set action shall support the following five forms: (1) direct snapshot (ALIAS.field), (2) calibrated average over N samples (CALIBRATE(ALIAS.field, N), N ≤ AMS_MAX_SENSOR_RETRY), (3) inter-sample delta (current minus previous reading), (4) running maximum across state lifetime (max(ALIAS.field)), (5) running minimum across state lifetime (min(ALIAS.field)). Any other form shall be a parse error.
VERIFICATION: Test
RATIONALE: AMS-4.8.2. Covers the five derived-variable forms implemented in parseSetActionCoreLocked. Closed form list prevents unbounded parser growth.
REFS: docs/standards/ams_standard.md AMS-4.8.2, src/config.h AMS_MAX_SENSOR_RETRY

[REQUIREMENT]
UID: SRS-2404
STATUS: Active
TAGS: AMS, Variables, ArithmeticExpression
STATEMENT: A set action shall support an arithmetic expression form "set VARNAME = TERM op TERM [op TERM]", where TERM is a sensor field reference (ALIAS.field), a declared variable name, or a float literal, and op is one of +, -, \*, /. Expressions with two or three terms shall be accepted; any other count shall be a parse error. Evaluation shall be strictly left-to-right. A literal zero in divisor position shall be a parse error. An unknown alias in a sensor term shall be a parse error. At runtime, if any operand is invalid (sensor failure, variable not yet set) or the result is NaN or infinite, an EVENT.warning shall be emitted and the target variable shall remain unchanged.
VERIFICATION: Test
RATIONALE: AMS-4.8.8. Allows missions to compute derived values (AGL altitude, average velocity) without consuming transition slots for intermediate logic.
REFS: docs/standards/ams_standard.md AMS-4.8.8

[REQUIREMENT]
UID: SRS-2402
STATUS: Active
TAGS: AMS, Variables, SensorFault
STATEMENT: If a set action or CALIBRATE call fails to produce a valid reading (sensor driver returns error or loss-of-fix), the target variable shall retain its previous value unchanged. The engine shall emit an EVENT.warning frame describing the failed field and shall NOT enter ERROR state.
VERIFICATION: Test
RATIONALE: AMS-5.7. Sensor faults during set actions must not halt the mission. Retaining the previous value preserves the last known good measurement in HK telemetry.
REFS: docs/standards/ams_standard.md AMS-5.7

[REQUIREMENT]
UID: SRS-2403
STATUS: Active
TAGS: AMS, Variables
STATEMENT: A named constant declared with "const NAME = VALUE" shall be immutable at runtime. Any AMS directive that attempts to modify a const (e.g. a set action targeting a const name) shall be a parse error detected at activation time, before the script begins executing.
VERIFICATION: Test
RATIONALE: AMS-4.12. Constants represent physical thresholds (e.g. apogee altitude, max g-load) that must not drift during a mission. Immutability is enforced at parse time to eliminate the runtime check overhead.
REFS: docs/standards/ams_standard.md AMS-4.12

[[/SECTION]]

[[SECTION]]
TITLE: 3.6 Scheduled Telemetry (HK / LOG)

[REQUIREMENT]
UID: SRS-2500
STATUS: Active
TAGS: AMS, Telemetry, HK
STATEMENT: Each state shall support at most AMS_MAX_HK_SLOTS (4) independent "every Nms: HK.report" blocks and at most AMS_MAX_HK_SLOTS (4) independent "log_every Nms: LOG.report" blocks. Each slot shall maintain its own independent elapsed timer, reset to zero on state entry. Slots do not share timers.
VERIFICATION: Test
RATIONALE: AMS-4.3.1. Independent cadences allow different HK field groups to be transmitted at different rates (e.g. GPS every 2 s, IMU every 500 ms) without inter-slot coupling.
REFS: docs/standards/ams_standard.md AMS-4.3.1, src/config.h AMS_MAX_HK_SLOTS

[REQUIREMENT]
UID: SRS-2501
STATUS: Active
TAGS: AMS, Telemetry, Limits
STATEMENT: The telemetry interval N in every Nms and log_every Nms directives shall satisfy TELEMETRY_INTERVAL_MIN ≤ N ≤ TELEMETRY_INTERVAL_MAX (100 ms ≤ N ≤ 60000 ms). Values outside this range shall be a parse error.
VERIFICATION: Test
RATIONALE: config.h bounds. Minimum 100 ms prevents overloading the LoRa link (2.4 kbps air rate); maximum 60 s prevents excessively stale telemetry from hiding in-flight anomalies.
REFS: src/config.h TELEMETRY_INTERVAL_MIN, TELEMETRY_INTERVAL_MAX

[REQUIREMENT]
UID: SRS-2502
STATUS: Active
TAGS: AMS, Telemetry, Arbitration
STATEMENT: The action arbitrator shall dispatch at most "budget" pending actions per tick, where budget is configured by the "priorities" directive (default 1, clamped to 1–3). Priority order within one tick shall be: EVENT > HK.report > LOG.report. Actions not dispatched in one tick shall remain pending for the next tick.
VERIFICATION: Test
RATIONALE: APUS-19.2. Bounding actions per tick limits per-tick radio TX time and prevents the AMS engine from monopolising the LoRa UART during peak telemetry load.
REFS: docs/standards/apus_standard.md APUS-19.2

[REQUIREMENT]
UID: SRS-2503
STATUS: Active
TAGS: AMS, Telemetry, HK
STATEMENT: An HK.report block shall include at most AMS_MAX_HK_FIELDS (16) named fields. Each field shall reference a sensor token (e.g. BARO.alt) or a global variable. Fields that reference an unknown token or undeclared variable shall be a parse error.
VERIFICATION: Test
RATIONALE: AMS-4.3 / APUS-15. Bounded field count ensures the serialised HK payload remains within the 200-byte maximum ARES Radio Protocol payload (SRS-3004).
REFS: docs/standards/ams_standard.md AMS-4.3, src/config.h AMS_MAX_HK_FIELDS

[[/SECTION]]

[[SECTION]]
TITLE: 3.7 Checkpoint Persistence

[REQUIREMENT]
UID: SRS-2600
STATUS: Active
TAGS: AMS, Checkpoint
STATEMENT: The engine shall write a checkpoint to AMS_RESUME_PATH on every state entry, on every execution enable/disable change, and periodically while in RUNNING status at an interval not exceeding AMS_CHECKPOINT_INTERVAL_MS (1000 ms). The checkpoint shall be written atomically: if the write fails, the previous valid checkpoint shall be preserved.
VERIFICATION: Test
RATIONALE: AMS-2. Frequent checkpointing maximises the recovery window after an in-flight crash. Atomic write prevents a partial checkpoint from replacing a valid one.
REFS: docs/standards/ams_standard.md AMS-2, src/config.h AMS_CHECKPOINT_INTERVAL_MS, AMS_RESUME_PATH

[REQUIREMENT]
UID: SRS-2601
STATUS: Active
TAGS: AMS, Checkpoint
STATEMENT: The checkpoint record (format v3) shall encode: format version tag, script filename, state index, executionEnabled flag, running flag, engine status, sequence counter, state elapsed time, per-slot HK elapsed times, per-slot LOG elapsed times, global variable values (float representation), and global variable validity flags.
VERIFICATION: Inspection
RATIONALE: AMS-2. All fields necessary to reconstruct engine runtime state exactly are captured. The validity flag distinguishes an uninitialised variable from a variable whose last read happened to be 0.0.
REFS: docs/standards/ams_standard.md AMS-2

[REQUIREMENT]
UID: SRS-2602
STATUS: Active
TAGS: AMS, Checkpoint, Compatibility
STATEMENT: The engine shall accept checkpoint records in formats v1, v2, and v3 on restore. An unrecognised format version tag, a truncated record, or a record whose script filename does not match the currently active script shall be silently discarded. The engine shall then start from the WAIT state without error.
VERIFICATION: Test
RATIONALE: AMS-2. Backward compatibility with older firmware versions ensures field upgrades do not require manual checkpoint deletion. Corrupt or mismatched checkpoints must not prevent boot.
REFS: docs/standards/ams_standard.md AMS-2

[REQUIREMENT]
UID: SRS-2603
STATUS: Active
TAGS: AMS, Checkpoint, Storage
STATEMENT: The checkpoint write operation shall be performed under the AMS engine mutex. No other task shall be able to read a partially written checkpoint file via the REST API while a write is in progress.
VERIFICATION: Inspection
RATIONALE: RTOS-4 / CERT-POSIX. A partial checkpoint seen by the restore path would produce undefined engine state. The mutex guarantees the LittleFS write completes or fails entirely before the file becomes visible to readers.
REFS: docs/standards/rtos_standard.md RTOS-4

[[/SECTION]]

[[SECTION]]
TITLE: 3.8 Telecommand (TC) Processing

[REQUIREMENT]
UID: SRS-2700
STATUS: Active
TAGS: AMS, TC
STATEMENT: The engine shall recognise the following TC tokens as valid transition condition operands: LAUNCH, ABORT, RESET, RESET_ABNORMAL. Each token, once set, is consumed atomically when a matching TC.command condition fires (SRS-2104). The pending TC slot holds at most one token at a time; injecting a second token before the first is consumed overwrites the first.
VERIFICATION: Test
RATIONALE: AMS-4.6 / AMS-5.3. Derived from the TcCommand enum. Single-token semantics prevent accidental ABORT being suppressed by a queued LAUNCH.
REFS: docs/standards/ams_standard.md AMS-4.6, AMS-5.3

[REQUIREMENT]
UID: SRS-2701
STATUS: Active
TAGS: AMS, TC, Debounce
STATEMENT: A TC condition qualified with "confirm N" (where 2 ≤ N ≤ 10) shall fire only after N injections of the same command are counted within the current state, without any intervening injection of a different command. A TC condition with no qualifier fires on the first injection.
VERIFICATION: Test
RATIONALE: AMS-4.11.3. Protects against spurious LoRa packet repetition triggering safety-critical commands such as ABORT.
REFS: docs/standards/ams_standard.md AMS-4.11.3

[REQUIREMENT]
UID: SRS-2702
STATUS: Active
TAGS: AMS, TC, RTOS
STATEMENT: The injectTc() method shall be callable from any RTOS task (API handler, radio dispatcher) and shall be protected by the AMS mutex with a finite timeout. It shall never be called from an ISR context.
VERIFICATION: Inspection
RATIONALE: RTOS-4 / CERT-SIG30. TC injection from the REST API runs on the API task; from radio on the comms task. Mutex protection prevents concurrent modification of the TC pending slot. ISR calls would violate FreeRTOS mutex semantics.
REFS: docs/standards/rtos_standard.md RTOS-4

[[/SECTION]]

[[SECTION]]
TITLE: 3.9 State Timeout Handler

[REQUIREMENT]
UID: SRS-2800
STATUS: Active
TAGS: AMS, OnTimeout
STATEMENT: A state may declare at most one on_timeout: block with the syntax "on_timeout Nms:" where N is a positive integer. If the state has been active for at least N milliseconds without any regular transition firing, the on_timeout handler shall execute: it shall dispatch the declared EVENT (if any), then execute the "transition to STATE" directive (if any). The handler shall fire at most once per state entry; after firing it shall not be re-armed within the same state visit.
VERIFICATION: Test
RATIONALE: AMS-4.10.3. Provides a named, annotated alternative to the bare fallback mechanism (SRS-2105) when an EVENT frame must accompany the forced transition (e.g. EVENT.warning before transitioning to SAFE). Unlike fallback, on_timeout is optional and allows an accompanying EVENT without requiring a destination state.
REFS: docs/standards/ams_standard.md AMS-4.10.3

[REQUIREMENT]
UID: SRS-2801
STATUS: Active
TAGS: AMS, OnTimeout, Limits
STATEMENT: An on_timeout: block shall accept at most one EVENT directive and at most one "transition to STATE" directive. A second on_timeout: block declared in the same state shall be a parse error. An on_timeout: block with neither an EVENT nor a transition directive shall be a parse error.
VERIFICATION: Test
RATIONALE: AMS-4.10.3. Exactly one on_timeout block per state prevents ambiguous timeout ordering. Requiring at least one action ensures the block is not a no-op that wastes a timer slot.
REFS: docs/standards/ams_standard.md AMS-4.10.3

[[/SECTION]]

[[SECTION]]
TITLE: 3.10 Buzzer Output (AMS-4.20)

[REQUIREMENT]
UID: SRS-2900
STATUS: Active
TAGS: AMS, Buzzer, OnEnter
STATEMENT: A state on_enter: block may contain at most AMS_MAX_BUZZER_ACTIONS (2) "BUZZER.beep Nms [Fhz] [Rx]" directives. When the engine enters the state, all declared BUZZER.beep actions shall be dispatched in declaration order via BuzzerInterface::beep(durationMs, freqHz, repeatCount). Each call shall be non-blocking; the buzzer stops automatically after the declared duration via an internal timer.
VERIFICATION: Test
RATIONALE: AMS-4.20. Provides deterministic, script-controlled audio feedback at state entry without blocking the AMS tick or requiring a dedicated RTOS task.
REFS: docs/standards/ams_standard.md AMS-4.20, src/config.h AMS_MAX_BUZZER_ACTIONS

[REQUIREMENT]
UID: SRS-2901
STATUS: Active
TAGS: AMS, Buzzer, Parser, Validation
STATEMENT: The parser shall reject a BUZZER.beep directive if: (a) the duration field is absent or not terminated with "ms"; (b) the duration value is outside [BUZZER_MIN_DURATION_MS, BUZZER_MAX_DURATION_MS] (50–10 000 ms); (c) a frequency suffix is present and the value is outside [BUZZER_MIN_FREQ_HZ, BUZZER_MAX_FREQ_HZ] (100–10 000 Hz); (d) more than AMS_MAX_BUZZER_ACTIONS (2) BUZZER.beep lines appear in the same on_enter: block; (e) a repeat count suffix is present and the value exceeds BUZZER_MAX_REPEAT_COUNT (8) or is zero. Any rejection shall set engine status to ERROR and store a descriptive error message.
VERIFICATION: Test
RATIONALE: AMS-4.20. Bounding duration and frequency prevents driver misuse on hardware (LEDC range, timer saturation). Limiting actions per state bounds StateDef memory.
REFS: src/config.h BUZZER_MIN_DURATION_MS, BUZZER_MAX_DURATION_MS, BUZZER_MIN_FREQ_HZ, BUZZER_MAX_FREQ_HZ, AMS_MAX_BUZZER_ACTIONS, BUZZER_MAX_REPEAT_COUNT

[REQUIREMENT]
UID: SRS-2902
STATUS: Active
TAGS: AMS, Buzzer, NullDriver
STATEMENT: If the BuzzerInterface pointer registered with the engine is null, all BUZZER.beep directives shall be silently skipped at runtime. The script shall parse, activate, and run normally. No error or warning status shall be set solely because the buzzer driver is null.
VERIFICATION: Test
RATIONALE: AMS-4.20. Allows buzzer-less hardware configurations to execute the same mission scripts without modification. Null-driver tolerance follows the same pattern as PulseInterface.
REFS: src/hal/buzzer/buzzer_interface.h

[REQUIREMENT]
UID: SRS-2903
STATUS: Active
TAGS: AMS, Buzzer, ExecutionGuard
STATEMENT: BUZZER.beep actions shall be dispatched only when the engine execution is enabled (executionEnabled\_ == true) and the engine status is RUNNING. If execution is disabled via setExecutionEnabled(false) after arm(), no BUZZER.beep actions shall fire on subsequent state entries or cadence ticks until execution is re-enabled.
VERIFICATION: Test
RATIONALE: AMS-4.20 / AMS-5.1. Consistent with the execution-enabled guard applied to PULSE.fire and EVENT actions. Prevents buzzer activation during ground-test or inhibited-flight modes.
REFS: docs/standards/ams_standard.md AMS-5.1

[REQUIREMENT]
UID: SRS-2904
STATUS: Active
TAGS: AMS, Buzzer, RepeatCount
STATEMENT: The BUZZER.beep directive shall accept an optional repeat-count suffix of the form "Rx" (e.g. "3x"), where R is an integer in the range [1, BUZZER_MAX_REPEAT_COUNT] (1–8). When count > 1, the driver shall play R beeps each of the declared duration, separated by silent gaps of the same duration, via a single non-blocking timer state machine (TONE/GAP phases). Omitting the suffix is equivalent to "1x".
VERIFICATION: Test
RATIONALE: AMS-4.20. Multi-beep patterns (e.g. three short beeps at deployment) are a common acoustic signal convention in rocketry. A timer-based approach keeps the AMS tick unblocked.
REFS: src/config.h BUZZER_MAX_REPEAT_COUNT

[REQUIREMENT]
UID: SRS-2905
STATUS: Active
TAGS: AMS, Buzzer, Every, Cadence
STATEMENT: A BUZZER.beep directive may appear at state scope immediately after an "every Nms:" header or after a "HK.report {}" block within that cadence scope. At most one BUZZER.beep directive is allowed per every: slot; a second occurrence in the same slot is a parse error. On each cadence tick the buzzer shall be fired before any HK telemetry frame is built and transmitted. A cadence slot containing only a BUZZER.beep directive (no HK.report fields) is valid; no HK radio packet is sent for that slot, only the buzzer fires.
VERIFICATION: Test
RATIONALE: AMS-4.20. Periodic audio feedback (e.g. descent beep every 500 ms) is useful for recovery operations. Reusing the existing every: cadence mechanism avoids adding a new timer primitive.
REFS: src/ams/mission_script_engine_types.h HkSlot.hasBuzzerAction

[[/SECTION]]

[[SECTION]]
TITLE: 3.11 Background Task Blocks

[REQUIREMENT]
UID: SRS-2920
STATUS: Active
TAGS: AMS, Tasks
STATEMENT: A script shall declare at most AMS_MAX_TASKS (4) background task blocks using the syntax "task NAME when in STATE [STATE...] every Nms:". A task block shall only execute when the current engine state appears in the task's "when in" clause. The "when in" clause shall accept at most AMS_MAX_TASK_ACTIVE_STATES (6) state names. Each task shall declare at most AMS_MAX_TASK_RULES (4) conditional if-rules.
VERIFICATION: Test
RATIONALE: AMS-4.13. Background tasks decouple periodic monitoring logic (e.g. maximum-altitude tracking, watchdog threshold checks) from the primary state machine transitions, keeping state blocks focused on flight events.
REFS: docs/standards/ams_standard.md AMS-4.13, src/config.h AMS_MAX_TASKS, AMS_MAX_TASK_RULES, AMS_MAX_TASK_ACTIVE_STATES

[REQUIREMENT]
UID: SRS-2921
STATUS: Active
TAGS: AMS, Tasks, Constraints
STATEMENT: A background task if-rule body shall execute set actions and dispatch at most one EVENT per rule firing. A task rule shall NOT contain a "transition to" directive; state transitions shall only occur via regular transitions, fallback, on_error, or on_timeout. Task-generated EVENTs shall be dispatched at the same priority as HK.report within the action arbitrator (SRS-2502).
VERIFICATION: Test
RATIONALE: AMS-4.13. Restricting tasks to set and EVENT prevents re-entrant state changes during task evaluation, which would violate the single-transition-per-tick constraint enforced by SRS-2106. Dispatching at HK priority avoids task events starving behind high-rate LOG traffic.
REFS: docs/standards/ams_standard.md AMS-4.13

[[/SECTION]]

[[SECTION]]
TITLE: 3.12 Pulse Channel Commands

[REQUIREMENT]
UID: SRS-2950
STATUS: Active
TAGS: AMS, PULSE
STATEMENT: An on_enter: block shall support at most AMS_MAX_PULSE_ACTIONS (4) PULSE.fire directives. Valid channel identifiers are A, B, C, and D, as well as any label declared via pulse.channel (SRS-2952). Each directive shall accept an optional duration override in the form "Nms" (positive integer, milliseconds); if omitted, the PULSE driver's configured default duration shall be used. PULSE.fire directives are only permitted inside on_enter: blocks; use in any other block context shall be a parse error. A channel referenced in PULSE.fire must have been previously declared with a pulse.channel directive; referencing an undeclared channel or unknown alias shall be a parse error.
VERIFICATION: Test
RATIONALE: AMS-4.17. Pyrotechnic firing is a one-shot action naturally associated with state entry (e.g. apogee detection triggers the ejection charge). Restricting PULSE.fire to on_enter: enforces that each firing is tied to exactly one state transition event and cannot be re-triggered by timer slots. Mandatory declaration (SRS-2952) provides an explicit safety audit trail for pyrotechnic channel usage.
REFS: docs/standards/ams_standard.md AMS-4.17, src/config.h AMS_MAX_PULSE_ACTIONS

[REQUIREMENT]
UID: SRS-2951
STATUS: Active
TAGS: AMS, PULSE, Safety
STATEMENT: A PULSE.fire action shall be executed synchronously by the PULSE driver during on_enter: block processing. If the driver rejects the fire command (hardware fault or safety interlock not armed), the engine shall immediately enter ERROR status. The PULSE hardware safety interlock shall be explicitly enabled via PUT /api/config before any script containing PULSE.fire directives can be armed; attempting to arm such a script with the interlock disabled shall return HTTP 409 Conflict.
VERIFICATION: Test
RATIONALE: AMS-4.17 / DO-178C. Pyrotechnic channels must fail-safe: a rejected fire must halt the mission rather than silently skip the firing, which could mask a wiring fault or produce an unsafe partial-sequence scenario. The interlock prevents accidental firing during bench test activations.
REFS: docs/standards/ams_standard.md AMS-4.17

[REQUIREMENT]
UID: SRS-2952
STATUS: Active
TAGS: AMS, PULSE, Safety
STATEMENT: A script shall declare every pulse channel it intends to use via a "pulse.channel X [as LABEL]" directive in the metadata section (before any state block). Valid channel letters are A, B, C, and D. Each channel may be declared at most once; a duplicate declaration shall be a parse error. The optional "as LABEL" clause assigns a human-readable alias; the label shall consist solely of alphanumeric characters and underscores, shall not exceed 15 characters, and shall be unique among all declared channel labels in the script. The parser shall emit a warning (LOG_W) if a declared channel is never referenced in any PULSE.fire directive.
VERIFICATION: Test
RATIONALE: AMS-4.18. Explicit declaration makes the pyrotechnic intent of a mission script visible to safety reviewers without requiring execution. Duplicate and alias-conflict checks prevent accidental re-assignment of a previously used channel. The unused-channel warning surfaces likely scripting mistakes early.
REFS: docs/standards/ams_standard.md AMS-4.18, src/config.h AMS_PULSE_LABEL_LEN

[[/SECTION]]

[[SECTION]]
TITLE: 3.13 Script Radio Configuration Override

[REQUIREMENT]
UID: SRS-2980
STATUS: Active
TAGS: AMS, RadioConfig
STATEMENT: A script may declare "radio.config PARAM_NAME = VALUE" directives in the metadata section (before any state block). Each directive overrides one APUS configuration parameter. Overrides shall be applied by the radio dispatcher immediately after a successful ARM command, before the first telemetry tick. Supported parameters include at minimum: "telem_interval" (ms, 100–60000) and "monitor.alt.high" (m, 0–15000). An unknown parameter name or a value outside its valid range shall be a parse error. At most one "radio.config" directive per parameter name is permitted; a duplicate is a parse error.
VERIFICATION: Test
RATIONALE: AMS-4.15. Mission-specific radio timing should be embedded in the script rather than requiring a separate PUT /api/config call, which risks misconfiguration between script upload and arm. Bounding parameters to a known table prevents injection of arbitrary radio register values.
REFS: docs/standards/ams_standard.md AMS-4.15

[[/SECTION]]
