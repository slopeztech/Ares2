[DOCUMENT]
TITLE: 4. Radio Telemetry (APUS)

[GRAMMAR]
ELEMENTS:
- TAG: REQUIREMENT
  FIELDS:
  - TITLE: UID
    TYPE: String
    REQUIRED: True
  - TITLE: STATUS
    TYPE: SingleChoice(Draft, Active, Deprecated)
    REQUIRED: True
  - TITLE: TAGS
    TYPE: Tag
    REQUIRED: False
  - TITLE: STATEMENT
    TYPE: String
    REQUIRED: True
  - TITLE: VERIFICATION
    TYPE: SingleChoice(Test, Inspection, Analysis, Review)
    REQUIRED: False
  - TITLE: RATIONALE
    TYPE: String
    REQUIRED: False
  - TITLE: REFS
    TYPE: String
    REQUIRED: False

[REQUIREMENT]
UID: SRS-3000
STATUS: Active
TAGS: Radio, APUS, Physical
STATEMENT: The firmware shall communicate over a DX-LR03-433T30D LoRa module at 433.125 MHz (LORA_FREQ_MHZ), 20 dBm TX power (LORA_TX_POWER), via UART2 at 9600 baud. The physical channel configuration shall be loaded from the active radio config at boot and persisted in flash.
VERIFICATION: Inspection
RATIONALE: APUS-1 / config.h. Physical link parameters are fixed for the current hardware revision. 433 MHz band provides adequate range for typical amateur rocket altitudes (< 3 km).
REFS: docs/standards/apus_standard.md APUS-1, src/config.h LORA_FREQ_MHZ, LORA_TX_POWER

[REQUIREMENT]
UID: SRS-3001
STATUS: Active
TAGS: Radio, APUS, Framing
STATEMENT: Every transmitted ARES Radio Protocol frame shall begin with the 4-byte sync word 0xAE 0x55 0xC3 0x1A. A receiver shall only begin frame parsing after detecting this exact sync sequence. Frames not preceded by the sync word shall be silently discarded.
VERIFICATION: Test
RATIONALE: APUS-4.3. The sync word provides frame alignment after link startup or mid-frame corruption. The 32-bit sequence was chosen for low probability of false-positive occurrence in arbitrary byte streams.
REFS: docs/standards/apus_standard.md APUS-4.3, docs/architecture/ares_radio_protocol.md

[REQUIREMENT]
UID: SRS-3002
STATUS: Active
TAGS: Radio, APUS, CRC
STATEMENT: Every transmitted frame shall include a CRC-32 field computed over bytes [4 .. 9+LEN] (excluding the sync word). Received frames whose CRC-32 does not match shall be silently discarded at the driver level. No corrupted data shall reach application logic.
VERIFICATION: Test
RATIONALE: APUS-1. The RF channel is noisy; bit-flip protection is mandatory. CRC-32 (Ethernet polynomial) provides a Hamming distance of 4 for frames up to 512 bytes.
REFS: docs/standards/apus_standard.md APUS-1.1, APUS-1.2, APUS-1.5, docs/architecture/ares_radio_protocol.md

[REQUIREMENT]
UID: SRS-3003
STATUS: Active
TAGS: Radio, APUS, Priority
STATEMENT: The radio dispatcher shall schedule frame transmission in priority order: EVENT (PUS ST[5]) > HK report (PUS ST[3]) > LOG. Within the same priority class, scheduling shall be round-robin across pending slots. A single dispatching cycle shall transmit at most one frame.
VERIFICATION: Inspection
RATIONALE: APUS-19. Safety-critical events (anomaly detection, state transitions) must not be starved by high-rate housekeeping telemetry.
REFS: docs/standards/apus_standard.md APUS-19

[REQUIREMENT]
UID: SRS-3004
STATUS: Active
TAGS: Radio, APUS, Payload
STATEMENT: A single ARES Radio Protocol frame payload shall not exceed 200 bytes. The HK telemetry payload shall be a fixed 78-byte struct (APUS-3.6), verified at compile time by a static_assert. Scripts that would produce an oversized HK payload due to too many fields shall be rejected at parse time with a descriptive error.
VERIFICATION: Test
RATIONALE: The ARES static Frame payload buffer and MAX_PAYLOAD_LEN limit a wire frame payload to 200 bytes. Oversized frames must be rejected rather than truncated. The 78-byte size is enforced by static_assert(sizeof(TelemetryPayload) == 78) in ares_radio_protocol.h.
REFS: docs/standards/apus_standard.md APUS-3.6, APUS-15, src/comms/ares_radio_protocol.h MAX_PAYLOAD_LEN, TelemetryPayload

[REQUIREMENT]
UID: SRS-3005
STATUS: Active
TAGS: Radio, APUS, NodeID
STATEMENT: The NODE field shall be an unsigned route endpoint: destination on uplink and source on downlink. Runtime telemetry node IDs shall be in the range NODE_ID_MIN (1) to NODE_ID_MAX (253), with 0 reserved for broadcast and 254–255 unavailable to runtime telemetry configuration. The firmware's telemetry source node ID shall be configurable via PUT /api/config.
VERIFICATION: Test
RATIONALE: APUS-10.5 defines the directional interpretation required because ARES carries one route byte rather than separate source and destination fields.
REFS: docs/standards/apus_standard.md APUS-10.1, APUS-10.5, src/config.h NODE_ID_MIN, NODE_ID_MAX

[REQUIREMENT]
UID: SRS-3006
STATUS: Active
TAGS: Radio, APUS, Security, Authentication
STATEMENT: When a 16-byte radio key is configured, every inbound non-fragmented COMMAND shall set FLAG_MAC and carry an 8-byte truncated HMAC-SHA256 tag over VER, FLAGS with FLAG_MAC set, NODE, TYPE, SEQ, command length, and command payload excluding the tag. The receiver shall compare the tag in constant time.
VERIFICATION: Test
RATIONALE: Authentication prevents command forgery over the RF link while retaining bounded static storage and an 8-byte wire overhead.
REFS: docs/standards/apus_standard.md APUS-4.8, APUS-4.9, src/comms/radio_mac.h, test/test_radio_protocol/test_radio_mac.cpp

[REQUIREMENT]
UID: SRS-3007
STATUS: Active
TAGS: Radio, APUS, Security, AntiReplay
STATEMENT: COMMAND authentication and freshness validation shall complete before any replay-window, queue, acceptance-ACK, or reassembly state is modified. A failed validation shall return HMAC_INVALID without consuming SEQ; a subsequent valid frame with that SEQ shall be accepted once and its authenticated replay shall be rejected.
VERIFICATION: Test
RATIONALE: Authenticate-before-state-change prevents an unauthenticated sender from exhausting chosen SEQ values and denying legitimate commands.
REFS: docs/standards/apus_standard.md APUS-4.7, APUS-4.9, src/comms/radio_dispatcher.cpp, test/test_dispatcher/test_command_dispatch.cpp TC-AUTH-7

[REQUIREMENT]
UID: SRS-3008
STATUS: Active
TAGS: Radio, APUS, Security, Time
STATEMENT: An authenticated COMMAND shall carry a ground-supplied estimate of receiver uptime in CommandHeader.timestampMs. At receipt the value shall be within plus or minus 5000 ms of receiver nowMs using wrap-safe uint32_t arithmetic; otherwise the receiver shall return HMAC_INVALID.
VERIFICATION: Test
RATIONALE: The authenticated freshness window prevents replay across reboot after the volatile SEQ bitmap resets. The field cannot represent independent sender uptime because the receiver compares it directly with its own clock.
REFS: docs/standards/apus_standard.md APUS-4.10, APUS-13.6, src/comms/ares_radio_protocol.h CMD_TIMESTAMP_WINDOW_MS, test/test_dispatcher/test_command_dispatch.cpp TC-AUTH-4 TC-AUTH-5 TC-AUTH-6

[REQUIREMENT]
UID: SRS-3009
STATUS: Active
TAGS: Radio, APUS, Security, OpenMode
STATEMENT: When no radio key is configured, the dispatcher shall preserve backwards-compatible open mode and may accept unsigned COMMAND frames. Open mode shall be identified as development or bench behavior and shall not be considered an authenticated flight configuration.
VERIFICATION: Test
RATIONALE: This records the current compatibility behavior without representing it as equivalent to an authenticated deployment.
REFS: docs/standards/apus_standard.md APUS-4.11, src/comms/radio_dispatcher.h, test/test_dispatcher/test_command_dispatch.cpp TC-AUTH-8

[REQUIREMENT]
UID: SRS-3010
STATUS: Active
TAGS: Radio, APUS, Security, Fragmentation
STATEMENT: While authenticated fragmented COMMAND transfer has no defined whole-transfer MAC contract, the receiver shall reject COMMAND frames carrying FLAG_FRAGMENT when a radio key is configured and shall return HMAC_INVALID without creating reassembly state.
VERIFICATION: Test
RATIONALE: Rejecting an undefined authenticated representation prevents fragments from bypassing COMMAND authentication or mutating unauthenticated session state.
REFS: docs/standards/apus_standard.md APUS-4.12, APUS-15, src/comms/radio_dispatcher.cpp checkCommandMac
